module brewerslab {

  namespace "http://brewerslabng.mellon-collie.net/yang/main";
  prefix "brewlabng";

  import brewerslab-types {
    prefix brewerslab-types;
  }
  import brewerslab-definitions {
    prefix brewerslab-definitions;
  }
  import brewerslab-recipes {
    prefix brewerslab-recipes;
  }
  import brewerslab-teststub {
    prefix brewerslab-teststub;
  }

  /* uses brewerslab-teststub:tests; */

  uses brewerslab-recipes:recipes;

}
