module voodoox {

  namespace "http://brewerslabng.mellon-collie.net/yang/vododoox";
  prefix "voodoox";

  import crux { prefix crux; }
  import integrationtest { prefix integrationtest; }
  container voodoox {
    uses integrationtest:itest;

    leaf ghost { 
      type string;
    }
  }
}
