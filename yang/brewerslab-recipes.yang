module brewerslab-recipes {

  namespace "http://brewerslabng.mellon-collie.net/yang/recipes";
  prefix "brewerslab-recipes";

  import brewerslab-types {
    prefix brewerslab-types;
  }

  import brewerslab-definitions {
    prefix brewerslab-definitions;
  }



  grouping recipes {
    list recipes {
      key "name version";

      leaf name {
        type string;
      }

      leaf id {
        type string;
      }

      leaf summary {
        type string;
      }

      leaf description {
        type string;
      }

      leaf version {
        type string;
      }

      leaf author {
        type string;
      }

      leaf process {
        type string;
      }

      container ingredients {

        list fermentables {
          key "name addat";

          leaf name {
            type leafref {
              path "/brewerslab-definitions:definitions/brewerslab-definitions:ingredients/brewerslab-definitions:fermentables/brewerslab-definitions:name";
            }
          }

          leaf addat {
            type brewerslab-types:fermentable-add-at;
          }

          leaf qty {
            type brewerslab-types:qty;
            mandatory true;
          }
        }

        list hops {
          key "name addat";

          leaf name {
            type leafref {
              path "/brewerslab-definitions:definitions/brewerslab-definitions:ingredients/brewerslab-definitions:hops/brewerslab-definitions:name";
            }
          }

          leaf addat {
            type brewerslab-types:hop-add-at;
          }

          leaf qty {
            type brewerslab-types:qty;
            mandatory true;
          }
        }
      }

      list yeast {
        key "name";

        leaf name {
          type leafref {
            path "/brewerslab-definitions:definitions/brewerslab-definitions:ingredients/brewerslab-definitions:yeast/brewerslab-definitions:name";
          }
        }

        leaf qty {
          type brewerslab-types:qty;
          mandatory true;
        }
      }

    }
  }
  uses recipes;
}
