module tester {
	namespace "http://confvillain.mellon-collie.net/tester/";
	prefix tester;

  leaf simplestleaf {
    type tester:typeA;
  }
  
  leaf simpleoper {
    type string;
    config false;
  }

  container tupperware {

    leaf oper {
      type string;
      config false;
    }

    leaf config {
      type string;
    }

    container outhere {
        
    }
    container outer {
      container inner {
        leaf number {
          type uint32;
        }
      }
    }
  }

  list simplelist {
    key id;

    leaf id {
      type string;
    }

    leaf val {
      type string;
    }

    leaf operval {
      type string;
      config false;
    }
  }

  container stackedlists {
    list lista {
      key keya;

      leaf keya {
        type string;
      }

      list listb {
        key keyb;

        leaf keyb {
          type string;
        }
      }
    }
  }

  container complex {
    leaf dec1 {
      type tester:typeB; 
    }

    leaf dec2 {
      type decimal64 {
        fraction-digits 2;
      }
    }
  }

  typedef typeA {
    type string;
  }

  typedef typeB {
    type decimal64 {
      fraction-digits 2;
    }
  }
}
